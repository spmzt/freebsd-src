// SPDX-License-Identifier: BSD-2-Clause
//
// Copyright (c) 2026 Pouria Mousavizadeh Tehrani <pouria@FreeBSD.org>

module freebsd-rtnetlink-route-snl {
  yang-version 1.1;
  namespace "urn:freebsd:yang:freebsd-rtnetlink-route-snl";
  prefix rtroute-snl;

  import freebsd-netlink-snl {
    prefix snl;
  }
  import freebsd-rtnetlink-route {
    prefix rtroute;
  }

  organization
    "FreeBSD";
  contact
    "Pouria Mousavizadeh Tehrani <pouria@FreeBSD.org>";
  description
    "The snl(3) parsers of the route messages: snl_rtm_route_parser
     and struct snl_parsed_route of <netlink/netlink_snl_route_parsers.h>,
     with the nexthops of a multipath route as struct rta_mpath_nh.";

  revision 2026-10-14 {
    description
      "Initial revision.";
  }

  snl:parser _mpath_nh_parser {
    snl:doc "Element of the NL_RTA_MULTIPATH array";
    snl:struct rta_mpath_nh;
    snl:grouping rtroute:multipath-nexthop;
    snl:nest metrics {
      snl:name _metrics_mp_nh_parser;
    }
    snl:member gw {
      snl:attr gateway;
      snl:attr via {
        snl:cb snl_attr_get_ipvia;
      }
      snl:scope-id ifindex;
    }
    snl:member ifindex {
      snl:type uint32_t;
      snl:field rtnh-ifindex;
    }
    snl:member rtnh_flags {
      snl:field rtnh-flags;
    }
    snl:member rtnh_weight {
      snl:field rtnh-hops;
    }
    snl:member rtax_mtu {
      snl:attr metrics/mtu;
    }
    snl:member rta_metric {
      snl:attr priority;
    }
    snl:member rta_rtflags {
      snl:attr rtflags;
    }
    snl:member rta_expire {
      snl:attr expires;
    }
  }

  snl:parser snl_rtm_route_parser {
    snl:doc "RTM_<NEW|DEL|GET>ROUTE message parser";
    snl:struct snl_parsed_route;
    snl:grouping rtroute:route-message;
    snl:nest metrics {
      snl:name _metrics_parser;
    }
    snl:code '
      static bool
      nlattr_get_multipath(struct snl_state *ss, struct nlattr *nla,
          const void *arg __unused, void *target)
      {
      	struct snl_parray *mpath = (struct snl_parray *)target;
      	uint32_t start_size = 4;

      	while (start_size < NLA_DATA_LEN(nla) / sizeof(struct rtnexthop))
      		start_size *= 2;

      	return (snl_attr_get_parray_sz(ss, nla, start_size,
      	    &_mpath_nh_parser, mpath));
      }';
    snl:member rta_dst {
      snl:attr dst;
      snl:scope-id rta_oif;
    }
    snl:member rta_gw {
      snl:attr gateway;
      snl:attr via {
        snl:cb snl_attr_get_ipvia;
      }
      snl:scope-id rta_oif;
    }
    snl:member rta_pref_src {
      snl:attr prefsrc;
    }
    snl:member rta_metrics {
      snl:type "struct nlattr *";
    }
    snl:member rta_multipath {
      snl:doc "Array of struct rta_mpath_nh";
      snl:type "struct snl_parray";
      snl:attr multipath;
      snl:cb nlattr_get_multipath;
    }
    snl:member rta_oif {
      snl:attr oif;
    }
    snl:member rta_expire {
      snl:attr expires;
    }
    snl:member rta_table {
      snl:attr table;
    }
    snl:member rta_knh_id {
      snl:attr knh-id;
    }
    snl:member rta_nh_id {
      snl:attr nh-id;
    }
    snl:member rta_rtflags {
      snl:attr rtflags;
    }
    snl:member rtax_mtu {
      snl:attr metrics/mtu;
    }
    snl:member rtax_weight {
      snl:attr weight;
    }
    snl:member rta_metric {
      snl:attr priority;
    }
    snl:member rtm_family {
      snl:field rtm-family;
    }
    snl:member rtm_type {
      snl:field rtm-type;
    }
    snl:member rtm_protocol {
      snl:field rtm-protocol;
    }
    snl:member rtm_dst_len {
      snl:field rtm-dst-len;
    }
  }
}
